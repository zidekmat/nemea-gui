module nemea-test-1 {
  yang-version 1.1;
  namespace "urn:ietf:params:xml:ns:yang:nemea-test-1";
  prefix "nemea-test-1";
  include trap-interfaces-test-1;
  organization "CESNET, z.s.p.o.";
  contact "cejkat@cesnet.cz";
  description "Module specifying configuration of Nemea supervisor.";
  revision "2018-01-17" { description "First version"; }

  grouping nemea-key-name {
    leaf name {
      type string {
        length "1..255";
        pattern "[0-9a-zA-Z _-]+";
      }
      mandatory true;
    }
  } // End grouping nemea-key-name

  grouping nemea-module-stats {
    /* This grouping is here just to make nemea-supervisor container
     *  more readable */
    container stats {
      config false;
      description "TODO";
    
      leaf running {
        type boolean;
        description "Specify whether the module is running.";
      }
      leaf restart-counter {
        type uint8;
        description "The number of repeated starts of the module.";
      }
      leaf cpu-user {
      	type uint64;
      	description "TODO";
      }
      leaf cpu-kern {
      	type uint64;
      	description "TODO";
      }
      leaf mem-vms {
      	type uint64;
      	description "TODO";
      }
      leaf mem-rss {
      	type uint64;
      	description "TODO";
      }
    }
  } // end grouping nemea-module-instance-stats


  container supervisor {
    list available-module {
      key name;
      uses nemea-key-name {
        description "Unique module name";
      }
      description "TODO";

      leaf path {
        type string { pattern "^/.+"; }
        mandatory true;
        description "Full path to where module binary resides.";
      }
      leaf description {
        type string;
        mandatory true;
        description "TODO";
      }
      leaf trap-monitorable {
        type boolean;
        mandatory true;
        description "TODO";
      }
      leaf trap-ifces-cli {
        type boolean;
        mandatory true;
        description "TODO";
      }
      leaf is-sysrepo-ready {
        type boolean;
        mandatory true;
        description "TODO";
      }


      choice if-is-sysrepo-ready {
        case yes {
          when "is-sysrepo-ready = 'true'";
          description "TODO";

          leaf sr-model-prefix {
            type string;
            mandatory true;
            description "Prefix of Sysrepo module to use for NEMEA module specific configuration";
          }
        }
      }
 
      
      choice if-using-trap-ifces {
        case yes {
          when "trap-ifces-cli = 'true'";
          description "TODO";

          leaf in-ifces-cnt {
            type string {
              length "1..2";
              pattern "(\\*|0|[1-9][0-9]?)";
            }
            mandatory true;
            description "exact cnt of ifces";
          }
          leaf out-ifces-cnt {
            type string {
              length "1..2";
              pattern "(\\*|0|[1-9][0-9]?)";
            }
            mandatory true;
            description "";
          }
        }
      }
    } // end list available-module

    list instance {
      key name;
      description "TODO";
      uses nemea-key-name {
        description "Unique module process name";
      }

      leaf module-ref {
        type leafref { path "../../available-module/name"; }
        mandatory true;
        description "TODO";
      }
      leaf enabled {
        type boolean;
        description "Activation of group of Nemea modules.";
      }
      leaf max-restarts-per-min {
        type uint8;
        default 3;
        description "How many times the module will be automatically restarted (in case it terminated) before setting disabled";
      }
      leaf last-pid {
        type uint32 { range "1..max"; }
        description "In case supervisor was interrupted and shouldn't have stopped the modules, PID of this Nemea module process is stored so that supervisor can reconnect to it once it starts again.";
      }
      
      /**
       * It would be nice to specify that we want to use trap-ifcs-list only if trap-ifces-cli is true, but then the subscription for runtime statistics to /nemea:supervisor/module/interface/stats would unfortunately not work.
       */
      uses trap-ifcs-list;
      uses nemea-module-stats;

      choice if-is-sysrepo-ready {
        when "deref(.)/../is-sysrepo-ready = true";
        // this is old: when "../available-module[name=current()/module-ref]/use-sysrepo";
        description "TODO";

        leaf use-sysrepo {
          type boolean;
          default false;
          description "Specifies whether module has it's own YANG model derived from Nemea module template and is capable of loading configuration from Sysrepo when passed -sr 'INSTANCE_NAME'. INSTANCE_NAME is TODO";
        }
      }

      choice if-isnt-sysrepo-ready-or-doesnt-use-sysrepo {
        when "deref(.)/../is-sysrepo-ready = false or use-sysrepo = false";
        // this is old: when "../available-module[name=current()/module-ref]/is-sysrepo-ready = 'false' or use-sysrepo = 'false'";
        description "TODO";
      
        leaf params {
          type string;
          description "TODO";
        }
      } // end choice is-module-sysrepo-ready
    } // end of list module
  } // end container nemea-supervisor
} // end module nemea-test-1
