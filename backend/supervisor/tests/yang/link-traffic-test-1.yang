module link-traffic-test-1 {
  namespace "urn:ietf:xml:ns:yang:link-traffic-test-1";
  prefix link-traffic-test-1;
  organization "CEZNET, z.s.p.o.";
  contact "hlavaj20@fit.cvut.cz";
  description "Module checks running links and counts traffic on them.";
  revision "2017-08-17" {
    description "Initial revision.";
  }
  revision "2018-01-30" {
    description "Update for new sysrepo enabled supervisor.";
  }

  list instance {
    key name;
    leaf name {
      type string {
        pattern "[ -_a-zA-Z0-9]*";
        length "1..100";
      }
    }
    container links {
      description "Links configuration parameters.";
      list link {
        key "link_id";
        description "List of links on the collector.";
        min-elements 1;
        leaf link_id {
          type uint8 {
            range "0..100";
          }
          mandatory true;
          description "Link number, used for internal purposes.";
        }
        leaf name {
          type string{
            pattern "[-_a-zA-Z0-9]*";
            length "1..100";
          }
          mandatory true;
          description "Name of link.";
        }
        leaf color {
          type string{
            pattern "[0-9a-fA-F]{6}";
          }
          description "Color for munin graphs.";
        }
      }
    } // end container links
  } // end list instance
} //TODO enabled linx
